RFC3062 DEFINITIONS
IMPLICIT TAGS
EXTENSIBILITY IMPLIED ::=

BEGIN

   -- asn1ate: 1.3.6.1.4.1.4203.1.11.1 -> { ... }
   passwdModifyOID OBJECT IDENTIFIER ::= { 1 3 6 1 4 1 4203 1 11 1 }

   -- asn1ate: added commas after [0] and [1] typedecls (ehm...)
   PasswdModifyRequestValue ::= SEQUENCE {
     userIdentity    [0]  OCTET STRING OPTIONAL,
     oldPasswd       [1]  OCTET STRING OPTIONAL,
     newPasswd       [2]  OCTET STRING OPTIONAL }

   PasswdModifyResponseValue ::= SEQUENCE {
     genPasswd       [0]     OCTET STRING OPTIONAL }

END
