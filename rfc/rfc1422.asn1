-- RFC1422 has been moved to HISTORIC status, yet it is included in RFC2315--

RFC1422 DEFINITIONS ::= BEGIN

   IMPORTS Name FROM RFC3280; --RFC1422 defines Name only textually!--

   --TODO: supplant the SIGNED MACRO, which is not defined anywhere--
   Certificate ::= --asn1ate:SIGNED-- SEQUENCE{
           version [0]     Version DEFAULT v1988,
           serialNumber    CertificateSerialNumber,
           signature       AlgorithmIdentifier,
           issuer          Name,
           validity        Validity,
           subject         Name,
           subjectPublicKeyInfo    SubjectPublicKeyInfo}

   Version ::=     INTEGER {v1988(0)}

   CertificateSerialNumber ::=     INTEGER

   Validity ::=    SEQUENCE{
           notBefore       UTCTime,
           notAfter        UTCTime}

   SubjectPublicKeyInfo ::=        SEQUENCE{
           algorithm               AlgorithmIdentifier,
           subjectPublicKey        BIT STRING}


   AlgorithmIdentifier ::= SEQUENCE{
           algorithm       OBJECT IDENTIFIER,
           parameters      ANY DEFINED BY algorithm OPTIONAL}

   --TODO: supplant the SIGNED MACRO, which is not defined anywhere--
   CertificateRevocationList ::= --asn1ate:SIGNED-- SEQUENCE{
           signature       AlgorithmIdentifier,
           issuer          Name,
           lastUpdate      UTCTime,
           nextUpdate      UTCTime,
           revokedCertificates
                           SEQUENCE OF CRLEntry OPTIONAL}

   CRLEntry ::= SEQUENCE{
           --RFCfix: userCertificate SerialNumber, --
           userCertificate CertificateSerialNumber,
           revocationDate UTCTime}

END
