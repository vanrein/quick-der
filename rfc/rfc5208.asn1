PKCS-8 {iso(1) member-body(2) us(840) rsadsi(113549) pkcs(1) pkcs-8(8)
         modules(1) pkcs-8(1)}

-- $Revision: 1.5 $

-- This module has been checked for conformance with the ASN.1
-- standard by the OSS ASN.1 Tools

DEFINITIONS IMPLICIT TAGS ::=

BEGIN

-- EXPORTS All --
-- All types and values defined in this module is exported for use in
-- other ASN.1 modules.

IMPORTS

-- asn1ate: informationFramework
-- asn1ate:          FROM UsefulDefinitions asn1ate: {joint-iso-itu-t(2) ds(5) module(1)
-- asn1ate:                                 asn1ate:  usefulDefinitions(0) 3}

-- asn1ate: Attribute
-- asn1ate:          FROM InformationFramework informationFramework

AlgorithmIdentifier -- asn1ate: , ALGORITHM-IDENTIFIER
         -- asn1ate: FROM PKCS-5 {iso(1) member-body(2) us(840) rsadsi(113549)
         -- asn1ate: pkcs(1) pkcs-5(5) modules(16) pkcs-5(1)};
	 FROM RFC2898
;

-- asn1ate: Define Attribute locally to avoid downward import spiral:

Attribute ::= SEQUENCE {
  -- asn1ate: type               ATTRIBUTE.&id({SupportedAttributes}),
  type               OBJECT IDENTIFIER,
  values
    -- asn1ate: SET SIZE (0..MAX) OF ATTRIBUTE.&Type({SupportedAttributes}{@type}),
    SET SIZE (0..MAX) OF ANY DEFINED BY type,
  valuesWithContext
    SET SIZE (1..MAX) OF
      -- asn1ate: SEQUENCE {value        ATTRIBUTE.&Type({SupportedAttributes}{@type}),
      SEQUENCE{value ANY DEFINED BY type,
                contextList  SET SIZE (1..MAX) OF Context} OPTIONAL
}

-- asn1ate: Define Context locally to avoid downward import spiral:

Context ::= SEQUENCE {
  --asn1ate: contextType    CONTEXT.&id({SupportedContexts}),
  contextType		OBJECT IDENTIFIER,
  contextValues
    --asn1ate: SET SIZE (1..MAX) OF CONTEXT.&Type({SupportedContexts}{@contextType}),
    SET SIZE (1..MAX) OF ANY DEFINED BY contextType,
  fallback       BOOLEAN DEFAULT FALSE
}


-- Private-key information syntax

PrivateKeyInfo ::= SEQUENCE {
   version Version,
   -- asn1ate: privateKeyAlgorithm AlgorithmIdentifier {{PrivateKeyAlgorithms}},
   privateKeyAlgorithm AlgorithmIdentifier,
   privateKey PrivateKey,
   attributes [0] Attributes OPTIONAL }

-- asn1ate: Version ::= INTEGER {v1(0)} (v1,...)
Version ::= INTEGER

PrivateKey ::= OCTET STRING

Attributes ::= SET OF Attribute

-- Encrypted private-key information syntax

EncryptedPrivateKeyInfo ::= SEQUENCE {
    -- asn1ate: encryptionAlgorithm AlgorithmIdentifier {{KeyEncryptionAlgorithms}},
    encryptionAlgorithm AlgorithmIdentifier,
    encryptedData EncryptedData
}

EncryptedData ::= OCTET STRING

-- asn1ate: PrivateKeyAlgorithms ALGORITHM-IDENTIFIER ::= {
-- asn1ate:      ... - - For local profiles
-- asn1ate: }
PrivateKeyAlgorithms ::= ANY

-- asn1ate: KeyEncryptionAlgorithms ALGORITHM-IDENTIFIER ::= {
-- asn1ate:      ... - - For local profiles
-- asn1ate: }
KeyEncryptionAlgorithms ::= ANY

END
